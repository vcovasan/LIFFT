# Installation Tool Requirements

## L-FUNC-040: The motor shall be able to apply at least 3.62Nm (Functional)
Functional

## L-FUNC-050: The controller shall account for actuator limits (Functional)

## L-FUNC-060: The controller shall maintain the output torque at the stress midpoint with at least 6dB Gain Margin (Functional)

## L-FUNC-070: The sensor shall provide optical RPM Measurements (Functional)

## L-FUNC-080: A debounce mechanism shall be implemented for the encoder output (Functional)
